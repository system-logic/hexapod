# -*- coding: utf-8 -*-
"""
Hexapod.FCMacro — full hexapod assembly built from one leg (SpiderLeg.FCStd)
============================================================================
What it does:
  1. Opens SpiderLeg.FCStd and combines all leg parts into one compound.
  2. Places 6 copies of the leg around an elongated hexagonal body.
     Left legs are NOT mirrored: they are the same leg rotated by 180 deg,
     exactly as on the real robot (servo mounts are one-sided).
  3. Builds the bottom deck. It replaces the Chassis pad of the leg file:
     the S1 servo body drops through a window in the deck and its flange
     is bolted to the deck with 4 x M3 (DS3218 flange pattern 49.5 x 10).
  4. Builds the top deck on six standoffs (protects the electronics and,
     together with the bottom deck, makes the body much stiffer).
  5. Mounts on the bottom deck:
       - Raspberry Pi (holes 58 x 49, M2.5) on printed-in standoffs
       - STM32F4-Discovery: the board has NO mounting holes, so it is held
         by 4 printed corner clips (DiscoCornerClip), one M3 screw each
       - 2 printed camera brackets at the front (stereo baseline 60 mm)
  6. Adds coloured mock-ups of the boards and cameras to check the layout.

Run: FreeCAD -> Macro -> Execute. SpiderLeg.FCStd is looked up next to this
macro, next to the active document, in the current directory, or set
LEG_FILE. SpiderLeg.FCStd itself is produced by cad/leg/Assembly_SpiderLeg
(see cad/build_all.py).
"""

import os
import math
import FreeCAD as App
import Part

# ----------------------------------------------------------------------------
# PARAMETERS (all dimensions in mm)
# ----------------------------------------------------------------------------
LEG_FILE = ""          # full path to SpiderLeg.FCStd; "" = search automatically

# --- body geometry -----------------------------------------------------------
DECK_T        = 4.0    # bottom deck thickness
TOP_DECK_T    = 3.0    # top deck thickness
DECK_MARGIN   = 38.0   # deck outline margin outward from the coxa axes
TOP_CLEAR     = 42.0   # gap between the decks (standoff height)
TOP_SCALE     = 0.72   # top deck = scaled-down bottom outline

# leg mounting points (coxa axis) and leg direction (deg, 0 = +X, CCW).
# Y+ is forward. Right side is X+.
LEG_MOUNTS = [
    # ( x,     y,    leg angle)
    (  70.0,  105.0,   45.0),   # right front
    (  92.0,    0.0,    0.0),   # right middle
    (  70.0, -105.0,  -45.0),   # right rear
    ( -70.0,  105.0,  135.0),   # left front
    ( -92.0,    0.0,  180.0),   # left middle
    ( -70.0, -105.0, -135.0),   # left rear
]

# --- leg interface (from SpiderLeg.FCStd, no need to change) ------------------
CHASSIS_TOP_Z   = -12.8            # top of the Chassis pad in the leg frame
CHASSIS_HOLES   = [(-24.75, -5.0), (24.75, -5.0), (-24.75, 5.0), (24.75, 5.0)]
CHASSIS_HOLE_R  = 1.6              # M3
SERVO_WINDOW    = (41.5, 20.6)     # window in the deck for the S1 servo body

# standoffs between the decks — outside the swing sector of every coxa
STANDOFF_PTS = [(0.0, 79.5), (0.0, -79.5),
                (63.6, 39.7), (-63.6, 39.7),
                (63.6, -39.7), (-63.6, -39.7)]
CABLE_HOLES  = [(-20.0, -6.0, 4.0), (20.0, -6.0, 4.0)]  # (x, y, radius)

# --- Raspberry Pi (3B/3B+/4B/5 footprint: board 85 x 56) ----------------------
RPI_POS        = (0.0, -44.0)      # board centre on the bottom deck (x, y)
RPI_ROT        = 0.0               # board rotation, deg
RPI_BOARD      = (85.0, 56.0, 1.6)
RPI_HOLES_DXDY = (58.0, 49.0)      # hole pattern
RPI_HOLE_R     = 1.35              # M2.5
RPI_STANDOFF_H = 6.0
RPI_MOCK_H     = 17.0              # mock-up height including connectors

# --- STM32F4-Discovery (board 97 x 66, NO mounting holes) ---------------------
# held by four printed corner clips (DiscoCornerClip), each fixed to the deck
# with one M3 screw outside the board corner.
DISCO_POS        = (0.0, 38.0)
DISCO_ROT        = 0.0
DISCO_BOARD      = (97.0, 66.0, 1.6)
DISCO_CLIP_PAD_H = 5.0             # clip shelf height = board-to-deck gap
DISCO_MOCK_H     = 14.0

# --- cameras (bracket hole pattern: Pi Camera v2 module 25 x 24, holes 21 x 12.5)
CAM_BASELINE   = 60.0              # stereo baseline (distance between cameras)
CAM_Y          = None              # None = at the front edge of the deck (auto)
CAM_H          = 34.0              # lens axis height above the bottom deck
CAM_PLATE_T    = 3.0
CAM_PLATE_W    = 30.0
CAM_PLATE_H    = 44.0
CAM_HOLES_DXDY = (21.0, 12.5)
CAM_HOLE_R     = 1.1               # M2 (d2.2 for screw + nut; 0.8 for self-tapping)

STANDOFF_R      = 4.0              # deck standoffs, M3 inside
STANDOFF_HOLE_R = 1.3              # pilot hole for an M3 thread in plastic

# ----------------------------------------------------------------------------
def find_leg_file():
    if LEG_FILE and os.path.isfile(LEG_FILE):
        return LEG_FILE
    cand = []
    try:
        cand.append(os.path.join(os.path.dirname(__file__), "SpiderLeg.FCStd"))
    except NameError:
        pass
    ad = App.ActiveDocument
    if ad and ad.FileName:
        cand.append(os.path.join(os.path.dirname(ad.FileName), "SpiderLeg.FCStd"))
    cand.append(os.path.join(os.getcwd(), "SpiderLeg.FCStd"))
    for c in cand:
        if os.path.isfile(c):
            return c
    if App.GuiUp:
        from PySide import QtWidgets
        f, _ = QtWidgets.QFileDialog.getOpenFileName(
            None, "Select SpiderLeg.FCStd", "", "FreeCAD (*.FCStd)")
        if f:
            return f
    raise RuntimeError("SpiderLeg.FCStd not found — set LEG_FILE at the top of the macro")


def load_leg_compound(path):
    """Returns (compound of all leg parts, list of (name, shape))."""
    already = None
    for d in App.listDocuments().values():
        if d.FileName and os.path.abspath(d.FileName) == os.path.abspath(path):
            already = d
            break
    doc = already or App.openDocument(path)
    shapes, named = [], []
    for o in doc.Objects:
        if o.Label.startswith("Chassis"):
            continue            # stand-in pad from the leg file; the deck replaces it
        if hasattr(o, "Shape") and not o.Shape.isNull():
            s = o.Shape.copy()
            shapes.append(s)
            named.append((o.Label, s))
    if not shapes:
        raise RuntimeError("No shapes found in the leg file")
    comp = Part.makeCompound(shapes)
    if already is None:
        App.closeDocument(doc.Name)
    return comp, named


def leg_placement(x, y, ang_deg):
    return App.Placement(App.Vector(x, y, 0),
                         App.Rotation(App.Vector(0, 0, 1), ang_deg))


def deck_outline(scale=1.0):
    """Convex outline through the leg mounting points, pushed outward by DECK_MARGIN."""
    pts = []
    # order the points by polar angle
    ordered = sorted(LEG_MOUNTS, key=lambda m: math.atan2(m[1], m[0]))
    for x, y, a in ordered:
        r = math.hypot(x, y)
        k = (r + DECK_MARGIN) / r * scale
        pts.append(App.Vector(x * k, y * k, 0))
    pts.append(pts[0])
    wire = Part.makePolygon(pts)
    return Part.Face(wire)


def make_deck(z0, thick, scale=1.0):
    face = deck_outline(scale)
    solid = face.extrude(App.Vector(0, 0, thick))
    solid.translate(App.Vector(0, 0, z0))
    return solid


def cyl(r, h, x, y, z):
    c = Part.makeCylinder(r, h)
    c.translate(App.Vector(x, y, z))
    return c


def rot_pt(px, py, ang_deg):
    a = math.radians(ang_deg)
    return (px * math.cos(a) - py * math.sin(a),
            px * math.sin(a) + py * math.cos(a))


def add_part(doc, name, shape, color=None, transparency=0):
    o = doc.addObject("Part::Feature", name)
    o.Shape = shape
    if App.GuiUp and color:
        o.ViewObject.ShapeColor = color
        o.ViewObject.Transparency = transparency
    return o


def board_mount(cx, cy, rot, holes_xy, hole_r, standoff_h, deck_top_z):
    """Board standoffs + list of global hole centres."""
    posts, holes = [], []
    for hx, hy in holes_xy:
        gx, gy = rot_pt(hx, hy, rot)
        gx += cx; gy += cy
        posts.append(cyl(3.2, standoff_h, gx, gy, deck_top_z))
        holes.append((gx, gy))
    return posts, holes


def make_corner_clip(board_t=1.6, pad_h=5.0, arm=12.0, lip=2.0, wall=2.0, boss=9.0):
    """Corner clip for a board without mounting holes. Local frame: the board
    occupies x>0, y>0 with its corner at (0,0); the M3 screw sits in a boss
    outside the corner at (-4.5, -4.5)."""
    V = App.Vector
    slot = board_t + 0.4
    top = pad_h + slot + 1.5
    b = Part.makeBox(boss, boss, pad_h, V(-boss, -boss, 0))
    b = b.fuse(Part.makeBox(arm + wall, 5 + wall, pad_h, V(-wall, -wall, 0)))
    b = b.fuse(Part.makeBox(5 + wall, arm + wall, pad_h, V(-wall, -wall, 0)))
    b = b.fuse(Part.makeBox(arm + wall, wall, top, V(-wall, -wall, 0)))
    b = b.fuse(Part.makeBox(wall, arm + wall, top, V(-wall, -wall, 0)))
    b = b.fuse(Part.makeBox(arm, lip, 1.5, V(0, 0, pad_h + slot)))
    b = b.fuse(Part.makeBox(lip, arm, 1.5, V(0, 0, pad_h + slot)))
    b = b.cut(Part.makeCylinder(1.7, pad_h + 2, V(-boss / 2, -boss / 2, -1)))
    return b.removeSplitter()


def make_camera_bracket():
    """Printed camera bracket. Local axes: X width, Y forward (camera on the
    +Y side, foot on the deck on the -Y side), Z up from the deck."""
    V = App.Vector
    T, W, H, FOOT = CAM_PLATE_T, CAM_PLATE_W, CAM_PLATE_H, 14.0
    b = Part.makeBox(W, T, H, V(-W / 2, 0, 0)).fuse(
        Part.makeBox(W, FOOT, T, V(-W / 2, -FOOT, 0)))
    for sx in (-1, 1):                                  # gussets
        x0 = sx * W / 2 - (2 if sx > 0 else 0)
        tri = Part.Face(Part.makePolygon(
            [V(x0, -FOOT + 1, T), V(x0, 0, T), V(x0, 0, H - 12), V(x0, -FOOT + 1, T)]))
        b = b.fuse(tri.extrude(V(2, 0, 0)))
    dx, dy = CAM_HOLES_DXDY
    for hx in (-dx / 2, dx / 2):                        # bosses + camera holes
        for hz in (CAM_H - dy / 2, CAM_H + dy / 2):
            b = b.fuse(Part.makeCylinder(2.4, 2.0, V(hx, T, hz), V(0, 1, 0)))
            b = b.cut(Part.makeCylinder(CAM_HOLE_R, T + 4, V(hx, -1, hz), V(0, 1, 0)))
    b = b.cut(Part.makeBox(18, T + 2, 4, V(-9, -1, 6)))  # ribbon cable slot
    for hx in (-9, 9):                                   # M3 into the deck
        b = b.cut(Part.makeCylinder(1.7, T + 2, V(hx, -8, -1)))
    return b.removeSplitter()


def main():
    leg_path = find_leg_file()
    App.Console.PrintMessage("Leg: %s\n" % leg_path)
    leg_comp, _ = load_leg_compound(leg_path)

    doc = App.newDocument("Hexapod")

    # ------------------------------------------------------------ 6 legs
    for i, (x, y, a) in enumerate(LEG_MOUNTS, 1):
        o = add_part(doc, "Leg%d" % i, leg_comp.copy(), color=(0.55, 0.57, 0.60))
        o.Placement = leg_placement(x, y, a)
        o.Label = "Leg_%d" % i

    # The deck takes the place of the leg's Chassis pad: the S1 servo body
    # drops through the window and its flange ears rest ON TOP of the deck.
    deck_top_z = CHASSIS_TOP_Z
    deck_bot_z = deck_top_z - DECK_T

    # ---------------------------------------------------- bottom deck
    deck = make_deck(deck_bot_z, DECK_T)
    # M3 holes for every leg (Chassis positions in the leg frame -> global)
    for x, y, a in LEG_MOUNTS:
        for hx, hy in CHASSIS_HOLES:
            gx, gy = rot_pt(hx, hy, a)
            deck = deck.cut(cyl(CHASSIS_HOLE_R, DECK_T + 2, x + gx, y + gy,
                                deck_bot_z - 1))
        # window for the S1 servo body
        w, h = SERVO_WINDOW
        win = Part.makeBox(w, h, DECK_T + 2)
        win.translate(App.Vector(-w / 2, -h / 2, deck_bot_z - 1))
        win.rotate(App.Vector(0, 0, deck_bot_z), App.Vector(0, 0, 1), a)
        win.translate(App.Vector(x, y, 0))
        deck = deck.cut(win)
    for cx_, cy_, cr_ in CABLE_HOLES:  # cable harness holes
        deck = deck.cut(cyl(cr_, DECK_T + 2, cx_, cy_, deck_bot_z - 1))

    # ------------------------------------------- Raspberry Pi mount
    rpi_holes_local = [(sx * RPI_HOLES_DXDY[0] / 2, sy * RPI_HOLES_DXDY[1] / 2)
                       for sx in (-1, 1) for sy in (-1, 1)]
    rpi_posts, rpi_pts = board_mount(RPI_POS[0], RPI_POS[1], RPI_ROT,
                                     rpi_holes_local, RPI_HOLE_R,
                                     RPI_STANDOFF_H, deck_top_z)

    # --------------------------- Discovery: 4 corner clips + deck holes
    clips = []
    for sx in (-1, 1):
        for sy in (-1, 1):
            cxl, cyl_ = sx * DISCO_BOARD[0] / 2, sy * DISCO_BOARD[1] / 2   # board corner
            ang = {(-1, -1): 0, (1, -1): 90, (1, 1): 180, (-1, 1): -90}[(sx, sy)]
            c = make_corner_clip(DISCO_BOARD[2], DISCO_CLIP_PAD_H)
            c.rotate(App.Vector(0, 0, 0), App.Vector(0, 0, 1), ang)
            gx, gy = rot_pt(cxl, cyl_, DISCO_ROT)
            c.translate(App.Vector(DISCO_POS[0] + gx, DISCO_POS[1] + gy, deck_top_z))
            clips.append(c)
            hx, hy = rot_pt(-4.5, -4.5, ang)
            hx, hy = rot_pt(cxl + hx, cyl_ + hy, DISCO_ROT)
            deck = deck.cut(cyl(1.7, DECK_T + 2, DISCO_POS[0] + hx, DISCO_POS[1] + hy,
                                deck_bot_z - 1))
    add_part(doc, "DiscoCornerClips", Part.makeCompound(clips), color=(0.15, 0.35, 0.85))

    for p in rpi_posts:
        deck = deck.fuse(p)
    for (gx, gy) in rpi_pts:
        deck = deck.cut(cyl(RPI_HOLE_R, DECK_T + RPI_STANDOFF_H + 2, gx, gy, deck_bot_z - 1))

    # -------------------------------------------------- deck standoffs
    top_z0 = deck_top_z + TOP_CLEAR
    standoff_pts = list(STANDOFF_PTS)
    posts = []
    for gx, gy in standoff_pts:
        p = cyl(STANDOFF_R, TOP_CLEAR, gx, gy, deck_top_z)
        p = p.cut(cyl(STANDOFF_HOLE_R, TOP_CLEAR + 2, gx, gy, deck_top_z - 1))
        posts.append(p)
    add_part(doc, "Standoffs", Part.makeCompound(posts), color=(0.3, 0.3, 0.35))

    # ------------------------------------------------- top deck
    top = make_deck(top_z0, TOP_DECK_T, TOP_SCALE)
    for gx, gy in standoff_pts:
        top = top.cut(cyl(1.7, TOP_DECK_T + 2, gx, gy, top_z0 - 1))
    add_part(doc, "TopDeck", top, color=(0.15, 0.15, 0.18), transparency=40)

    # -------------------------------------------- camera brackets
    ymax = max(v.Point.y for v in deck_outline().Vertexes)
    cam_y = CAM_Y if CAM_Y is not None else ymax - CAM_PLATE_T
    cam_shapes, cam_mocks = [], []
    for sx in (-1, 1):
        cx = sx * CAM_BASELINE / 2
        br = make_camera_bracket()
        br.translate(App.Vector(cx, cam_y, deck_top_z))
        cam_shapes.append(br)
        # matching M3 holes in the deck for the bracket foot
        for hx in (-9, 9):
            deck = deck.cut(cyl(1.7, DECK_T + 2, cx + hx, cam_y - 8, deck_bot_z - 1))
        zc = deck_top_z + CAM_H
        m = Part.makeBox(25, 1.2, 24)
        m.translate(App.Vector(cx - 12.5, cam_y + CAM_PLATE_T + 2, zc - 12))
        lens = Part.makeCylinder(4.0, 5, App.Vector(cx, cam_y + CAM_PLATE_T + 3.2, zc + 3),
                                 App.Vector(0, 1, 0))
        cam_mocks.append(m.fuse(lens))
    add_part(doc, "CameraBrackets", Part.makeCompound(cam_shapes),
             color=(0.85, 0.55, 0.10))
    add_part(doc, "Cameras_mock", Part.makeCompound(cam_mocks),
             color=(0.10, 0.60, 0.25))

    add_part(doc, "BottomDeck", deck, color=(0.15, 0.15, 0.18))

    # ------------------------------------------------ board mock-ups
    def board_mock(name, pos, rot, size, mock_h, standoff_h, color):
        b = Part.makeBox(size[0], size[1], mock_h)
        b.translate(App.Vector(-size[0] / 2, -size[1] / 2, 0))
        b.rotate(App.Vector(0, 0, 0), App.Vector(0, 0, 1), rot)
        b.translate(App.Vector(pos[0], pos[1], deck_top_z + standoff_h))
        add_part(doc, name, b, color=color, transparency=30)

    board_mock("RaspberryPi_mock", RPI_POS, RPI_ROT, RPI_BOARD,
               RPI_MOCK_H, RPI_STANDOFF_H, (0.0, 0.45, 0.15))
    board_mock("STM32F4Disco_mock", DISCO_POS, DISCO_ROT, DISCO_BOARD,
               DISCO_MOCK_H, DISCO_CLIP_PAD_H, (0.05, 0.25, 0.65))

    doc.recompute()
    out = os.path.join(os.path.dirname(leg_path)
                       if os.access(os.path.dirname(leg_path), os.W_OK)
                       else os.path.expanduser("~"), "Hexapod.FCStd")
    try:
        doc.saveAs(out)
        App.Console.PrintMessage("Saved: %s\n" % out)
    except Exception as e:
        App.Console.PrintMessage("Could not save automatically: %s\n" % e)

    if App.GuiUp:
        import FreeCADGui as Gui
        Gui.ActiveDocument.ActiveView.viewAxometric()
        Gui.SendMsgToActiveView("ViewFit")
    return doc


if __name__ != "hexapod_lib":
    main()
