# ============================================================
#  DS3218 — servo reference model (for fitting / assembly). DO NOT PRINT.
#  Dimensions per datasheet: body 40 x 20 x 40.5, mounting flange at 27.7 mm,
#  flange holes 49.5 x 10 mm (M3), 25T spline, d 5.9.
# ============================================================
import FreeCAD as App
import Part

doc = App.ActiveDocument
if doc is None:
    doc = App.newDocument("SpiderLeg")
V = App.Vector

# ---------- PARAMETERS ----------
SV_L, SV_W, SV_H = 40.0, 20.0, 40.5
EAR_W, EAR_T, FLANGE_Z = 54.5, 2.5, 27.7        # flange ears: span / thickness / height
HOLE_DX, HOLE_DY, FLANGE_D = 49.5, 10.0, 3.2    # flange hole rectangle (M3)
SHAFT_X, SHAFT_Y = 20.0, 10.0
SPLINE_D, SHAFT_EXP = 6.0, 5.0
HOX, HOY = HOLE_DX / 2, HOLE_DY / 2

# ---------- GEOMETRY ----------
s = Part.makeBox(SV_L, SV_W, SV_H)
ears = Part.makeBox(EAR_W, SV_W, EAR_T); ears.translate(V(-(EAR_W - SV_L) / 2, 0, FLANGE_Z))
s = s.fuse(ears)
# 4 real flange mounting holes (49.5 x 10)
for hx in (SHAFT_X - HOX, SHAFT_X + HOX):
    for hy in (SHAFT_Y - HOY, SHAFT_Y + HOY):
        s = s.cut(Part.makeCylinder(FLANGE_D / 2, EAR_T + 2, V(hx, hy, FLANGE_Z - 1)))
# boss + spline shaft on the top cover
s = s.fuse(Part.makeCylinder(7.5, 3, V(SHAFT_X, SHAFT_Y, SV_H)))
s = s.fuse(Part.makeCylinder(SPLINE_D / 2, SHAFT_EXP, V(SHAFT_X, SHAFT_Y, SV_H + 3)))
# cover screws (cosmetic)
for cx in (4.5, 35.5):
    for cy in (4.5, 15.5):
        s = s.cut(Part.makeCylinder(1.1, 2, V(cx, cy, SV_H - 2)))

obj = Part.show(s, "DS3218")
doc.recompute()
try:
    import FreeCADGui as Gui
    Gui.SendMsgToActiveView("ViewFit")
except Exception:
    pass
print("DS3218: servo model with the real flange (49.5 x 10). Do not print.")
