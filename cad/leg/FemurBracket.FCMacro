# ============================================================
#  FemurBracket — bracket for servo S2. PRINT.
#  Holds the servo by its REAL flange: body opening + 4 holes 49.5 x 10.
#  The servo body drops into the opening; the flange is clamped by 4 x M3.
# ============================================================
import FreeCAD as App
import Part

doc = App.ActiveDocument
if doc is None:
    doc = App.newDocument("SpiderLeg")
V = App.Vector

# ---------- PARAMETERS ----------
FB_BX, FB_BY, FB_BZ = 62.0, 26.0, 4.0          # base
FB_WALL_T, FB_YW, FB_WALL_H = 4.0, 26.0, 46.0  # wall
FB_S2_X, FB_S2_Z = 31.0, 28.0                  # S2 shaft centre on the wall
FB_BASE_HOLE_X, FB_BASE_HOLE_Y = 31.0, (6.0, 20.0)   # bolts to CoxaArm (M5)
# DS3218 flange (matches the servo model):
HOLE_DX, HOLE_DY, FLANGE_D = 49.5, 10.0, 3.2
HOX, HOY = HOLE_DX / 2, HOLE_DY / 2
CUT_L, CUT_W = 42.0, 22.0                       # body opening (40 x 20 + clearance)

# ---------- GEOMETRY ----------
b = Part.makeBox(FB_BX, FB_BY, FB_BZ)
wall = Part.makeBox(FB_BX, FB_WALL_T, FB_WALL_H); wall.translate(V(0, FB_YW - FB_WALL_T, 0))
b = b.fuse(wall)
g1 = Part.makeBox(10, FB_YW - FB_WALL_T, 16)
g2 = Part.makeBox(10, FB_YW - FB_WALL_T, 16); g2.translate(V(FB_BX - 10, 0, 0))
b = b.fuse(g1).fuse(g2)
for hy in FB_BASE_HOLE_Y:
    b = b.cut(Part.makeCylinder(5.2 / 2, FB_BZ + 2, V(FB_BASE_HOLE_X, hy, -1)))

# flange joint: body opening + 4 holes (drilled along +Y through the wall)
y0, y1 = FB_YW - FB_WALL_T, FB_YW
h = (y1 - y0) + 2
cut = Part.makeBox(CUT_L, h, CUT_W); cut.translate(V(FB_S2_X - CUT_L / 2, y0 - 1, FB_S2_Z - CUT_W / 2))
b = b.cut(cut)
for hx in (FB_S2_X - HOX, FB_S2_X + HOX):
    for hz in (FB_S2_Z - HOY, FB_S2_Z + HOY):
        b = b.cut(Part.makeCylinder(FLANGE_D / 2, h, V(hx, y0 - 1, hz), V(0, 1, 0)))

# slots for the CoxaArm ribs (the ribs enter the base from below).
# CoxaArm ribs: x28-58, y7-11 / y21-25; assembly offset coxa -> bracket = -(33, 3)
# => in the bracket frame the ribs sit at y4-8 / y18-22, x from 0 to ~25.
RIB_T, RIB_CLR = 4.0, 0.4                       # rib thickness and print clearance
slot_y = (4.0, 18.0)                            # lower slot edges (bracket frame)
slot_x0, slot_len, slot_h = -0.5, 27.0, 8.5     # open at the x=0 end; up to x~26.5 (< bolts at x=31)
for sy in slot_y:
    s = Part.makeBox(slot_len, RIB_T + 2 * RIB_CLR, slot_h)
    s.translate(V(slot_x0, sy - RIB_CLR, -0.5))
    b = b.cut(s)

obj = Part.show(b, "FemurBracket")
doc.recompute()
try:
    import FreeCADGui as Gui
    Gui.SendMsgToActiveView("ViewFit")
except Exception:
    pass
print("FemurBracket: flange clamp for S2. Print base-down.")
